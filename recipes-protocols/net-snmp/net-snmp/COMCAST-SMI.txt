-- File Name : COMCAST-SMI
-- Date      : Fri May 14 13:26:40 EDT 2010
-- Author    : WebNMS Agent Toolkit Java Edition - MIB Editor 6



COMCAST-SMI	DEFINITIONS ::= BEGIN
	IMPORTS
--		xcalibur
--			FROM COMCAST-SMI
		dod, enterprises, MODULE-IDENTITY, OBJECT-IDENTITY
			FROM SNMPv2-SMI;

	comcast	MODULE-IDENTITY
		LAST-UPDATED	"201004131613Z"
		ORGANIZATION	"Organization"
		CONTACT-INFO	"Contact-info"
		DESCRIPTION		"Description"
		REVISION		"201004131613Z"
		DESCRIPTION		""
		::=  {  enterprises  17270  }

	internet OBJECT IDENTIFIER
		::=  {  dod  1  }

	private	OBJECT IDENTIFIER
		::=  {  internet  4  }

	enterprises OBJECT IDENTIFIER
		::=  {  private  1  }

	xcalibur	OBJECT-IDENTITY
		STATUS			current
		DESCRIPTION		"Xcalibur Client Components namespace"
		::=  {  comcast  9225  }

END
