VIVIDLOGIC-MIB DEFINITIONS ::= BEGIN

IMPORTS
    Integer32,
    Unsigned32,
    Counter32,
    TimeTicks,
    OBJECT-TYPE,
    MODULE-IDENTITY,
    OBJECT-IDENTITY
        FROM SNMPv2-SMI               -- RFC 2578
    AutonomousType,
    DisplayString,
    TruthValue,
    RowPointer,
    TimeStamp,
    PhysAddress,
    MacAddress,
    TEXTUAL-CONVENTION
        FROM SNMPv2-TC                -- RFC 2579
    SnmpAdminString
        FROM SNMP-FRAMEWORK-MIB       -- RFC 3411
    enterprises			FROM SNMPv2-SMI
;

vividlogicmib  MODULE-IDENTITY
      LAST-UPDATED    "0209200000Z" -- September 20, 2002
      ORGANIZATION    "Vividloigc Inc"
      CONTACT-INFO
          "Ram Balaraman
           Postal: VividLoigc Inc,
	            40994 Encyclopedia Circle,
		    Fremont, CA, 94538
		    U.S.A.
           Phone:  +1 (510) 979-1394
           Fax:    +1 
           E-mail: ram@vividlogic.com"
    DESCRIPTION
            "This MIB module supplies the basic management object categories for Vividlogic"
    ::= { enterprises 31800 }

--
-- top level structure
--
VividLogicInfo                 OBJECT IDENTIFIER ::= { vividlogicmib 1 }
OcapCertificateinfo            OBJECT IDENTIFIER ::= { vividlogicmib 2 }
IEEE1394Certificateinfo        OBJECT IDENTIFIER ::= { vividlogicmib 3 }
MCardinfoCertificaton          OBJECT IDENTIFIER ::= { vividlogicmib 4 }
--
-- Example scalars
--

VividLogicAdd  OBJECT-TYPE
    SYNTAX      SnmpAdminString
    MAX-ACCESS  read-only
    STATUS      current
    DESCRIPTION
	"This is a simple object tell about the Vividlogic Inc address information"
    ::= { VividLogicInfo 1 }

VividLogicCEO  OBJECT-TYPE
    SYNTAX      SnmpAdminString
    MAX-ACCESS  read-only
    STATUS      current
    DESCRIPTION
	"This is a simple object tell about the Vividlogic Inc CEO info"
    ::= { VividLogicInfo 2 }

VividLogicVicePresident OBJECT-TYPE
    SYNTAX      SnmpAdminString
    MAX-ACCESS  read-only
    STATUS      current
    DESCRIPTION
	"This is a simple object tell about the Vividlogic Inc Vice-President"
    ::= { VividLogicInfo 3 }

VividLogicYearstarted OBJECT-TYPE
    SYNTAX      INTEGER
    MAX-ACCESS  read-only
    STATUS      current
    DESCRIPTION
	"This is a simple object tell about the Vividlogic Inc Year-started"
    ::= { VividLogicInfo 4 }


--
--  VIVIDLOGIC IEEE 1394 CERTIFICATION INFO
--

Ieee1394certificationObjects OBJECT IDENTIFIER ::= { IEEE1394Certificateinfo 1 }

Ieee1394certificationTable OBJECT-TYPE
    SYNTAX      SEQUENCE OF VividlogicIEEE1394certificationEntry
    MAX-ACCESS  not-accessible
    STATUS      current
    DESCRIPTION
            "This table contains attributes associated with the
            VividLogic CertificatationInfo of IEEE 1394."
    ::= { Ieee1394certificationObjects 1 }

IEEE1394certificationEntry OBJECT-TYPE
    SYNTAX      VividlogicIEEE1394certificationEntry
    MAX-ACCESS  not-accessible
    STATUS      current
    DESCRIPTION
            "An entry exists in this table for each
            interface of the type IEEE 1394."
    INDEX { VividlogicCEFInterfaceIndex }
    ::= { Ieee1394certificationTable 1 }

VividlogicIEEE1394certificationEntry ::=
    SEQUENCE {
       VividlogicCEFInterfaceIndex   Unsigned32,               -- Index for the Table 
       VividlogicSzDispString     SnmpAdminString,             -- //e.g. "xyz Certificate Info" e.g "1394 Certificate Info"
       VividlogicSzKeyInfoString  SnmpAdminString,             -- // usually empty
       VividlogicSzMfrName        SnmpAdminString,
       VividlogicSzModelName      SnmpAdminString,
       VividlogicAcModelId        DisplayString (SIZE(4)),     --  four Bytes [4]
       VividlogicAacVendorId      DisplayString (SIZE(3)),
       VividlogicAacDeviceId      DisplayString (SIZE(5)),
       VividlogicAacGUIDorMACADDR DisplayString (SIZE(4)),
       VividlogicBCertAvailable  TruthValue,                  -- boolen var (O or 1 / True/False)
       VividlogicBbCertValid     TruthValue,
       VividlogicBbIsProduction  TruthValue
  }

VividlogicCEFInterfaceIndex OBJECT-TYPE
    SYNTAX      Unsigned32(1..4294967295)
    MAX-ACCESS  not-accessible
    STATUS      current
    DESCRIPTION
            "The unique identifier of the Certification entry."
    ::= { IEEE1394certificationEntry 1 }


VividlogicSzDispString OBJECT-TYPE
    SYNTAX      SnmpAdminString
    MAX-ACCESS  read-only
    STATUS      current
    DESCRIPTION
            "This object allows the manager to retrieve the
            VividLogic IEEE1394 DTCP Certificate Info."
    ::= { IEEE1394certificationEntry 2 }

VividlogicSzKeyInfoString OBJECT-TYPE
    SYNTAX      SnmpAdminString
    MAX-ACCESS  read-only
    STATUS      current
    DESCRIPTION
            "This object allows the manager to retrieve the
            Keys / BOUND Info."
    ::= { IEEE1394certificationEntry 3 }

VividlogicSzMfrName OBJECT-TYPE
    SYNTAX      SnmpAdminString
    MAX-ACCESS  read-only
    STATUS      current
    DESCRIPTION
            "This object allows the manager to retrieve the
              Manufacture Name."
    ::= { IEEE1394certificationEntry 4 }

VividlogicSzModelName OBJECT-TYPE
    SYNTAX      SnmpAdminString
    MAX-ACCESS  read-only
    STATUS      current
    DESCRIPTION
            "This object allows the manager to retrieve the
            Model Name ."
    ::= { IEEE1394certificationEntry 5 }

VividlogicAcModelId OBJECT-TYPE
    SYNTAX      DisplayString (SIZE(4))
    MAX-ACCESS  read-only
    STATUS      current
    DESCRIPTION
            "This object allows the manager to retrieve the
             Model ID."
    ::= { IEEE1394certificationEntry 6 }

VividlogicAacVendorId OBJECT-TYPE
    SYNTAX      DisplayString (SIZE(3))
    MAX-ACCESS  read-only
    STATUS      current
    DESCRIPTION
            "This object allows the manager to retrieve the
            AacVendor Id."
    ::= { IEEE1394certificationEntry 7 }

VividlogicAacDeviceId OBJECT-TYPE
    SYNTAX      DisplayString (SIZE(5))
    MAX-ACCESS  read-only
    STATUS      current
    DESCRIPTION
            "This object allows the manager to retrieve the
             Aac Device ID."
    ::= { IEEE1394certificationEntry 8 }

VividlogicAacGUIDorMACADDR OBJECT-TYPE
    SYNTAX      DisplayString (SIZE(4))
    MAX-ACCESS  read-only
    STATUS      current
    DESCRIPTION
            "This object allows the manager to retrieve the
             AacGUIDorMACADDR."
    ::= { IEEE1394certificationEntry 9 }

VividlogicBCertAvailable OBJECT-TYPE
    SYNTAX      TruthValue
    MAX-ACCESS  read-only
    STATUS      current
    DESCRIPTION
            "The value 'true' indicates that the Certification Available
             . 'false' means the No Certification Avalibale."
    ::= { IEEE1394certificationEntry 10 }
VividlogicBbCertValid OBJECT-TYPE
    SYNTAX      TruthValue
    MAX-ACCESS  read-only
    STATUS      current
    DESCRIPTION
            "The value 'true' indicates that the Certification valid/Available
             . 'false' means the No Certification Avalibale."
    ::= { IEEE1394certificationEntry 11 }

VividlogicBbIsProduction OBJECT-TYPE
    SYNTAX      TruthValue
    MAX-ACCESS  read-only
    STATUS      current
    DESCRIPTION
            "The value 'true' indicates that the Certification valid/Available
             'false' means the No Certification Avalibale."
    ::= { IEEE1394certificationEntry 12 }

--
--  VIVIDLOGIC M-card Host  CERTIFICATION INFO
--

McardcertificationObjects OBJECT IDENTIFIER ::= { MCardinfoCertificaton 1 }

McardcertificationTable OBJECT-TYPE
    SYNTAX      SEQUENCE OF VividlogicIEEE1394certificationEntry
    MAX-ACCESS  not-accessible
    STATUS      current
    DESCRIPTION
            "This table contains attributes associated with the
            VividLogic CertificatationInfo of IEEE 1394."
    ::= { McardcertificationObjects 1 }

McardcertificationEntry OBJECT-TYPE
    SYNTAX      VividlogicMcardcertificationEntry
    MAX-ACCESS  not-accessible
    STATUS      current
    DESCRIPTION
            "An entry exists in this table for each
            interface of the type M-Card."
    INDEX { VividlogicMcardInterfaceIndex }
    ::= { McardcertificationTable 1 }

VividlogicMcardcertificationEntry ::=
    SEQUENCE {
       VividlogicMcardInterfaceIndex                 Unsigned32,               -- Index for the Table 
       VividlogicMcardSzDispString                   DisplayString (SIZE(512)),  -- // String" Displays "M-card Host Certificate Info"
       VividlogicMcardSzDeviceCertSubjectName        DisplayString (SIZE(512)),             -- // Subject string
       VividlogicMcardSzDeviceCertIssuerName         DisplayString (SIZE(512)),        -- // Issuer string
       VividlogicMcardSzManCertSubjectName           DisplayString (SIZE(512)),        -- // subject string
       VividlogicMcardSzManCertIssuerName            DisplayString (SIZE(512)),        -- // Issuer string
       VividlogicMcardAcHostId                       DisplayString (SIZE(5)),          --  four Bytes [5]
       VividlogicMcardbCertAvailable                 DisplayString (SIZE(4)),          --  four Bytes [4]
       VividlogicMcardbCertValid                     DisplayString (SIZE(4)),          --  four Byes [4]           
       VividlogicMcardbVerifiedWithChain             DisplayString (SIZE(4)),          --  four Bytes [4]
       VividlogicMcardbIsProduction                  DisplayString (SIZE(4)),          --  four Bytes [4] 
  }

VividlogicMcardInterfaceIndex OBJECT-TYPE
    SYNTAX      Unsigned32(1..4294967295)
    MAX-ACCESS  not-accessible
    STATUS      current
    DESCRIPTION
            "The unique identifier of the M-Card Certification entry."
    ::= { McardcertificationEntry 1 }


VividlogicSzDispString OBJECT-TYPE
    SYNTAX      DisplayString (SIZE(512))
    MAX-ACCESS  read-only
    STATUS      current
    DESCRIPTION
            "This object allows the manager to retrieve the
            VividLogic M-card Host Certificate Info."
    ::= { McardcertificationEntry 2 }

VividlogicMcardSzDeviceCertSubjectName OBJECT-TYPE
    SYNTAX      DisplayString (SIZE(512))
    MAX-ACCESS  read-only
    STATUS      current
    DESCRIPTION
            "This object allows the manager to retrieve the
            Subject Name Info."
    ::= { McardcertificationEntry 3 }

VividlogicMcardSzDeviceCertIssuerName OBJECT-TYPE
    SYNTAX      DisplayString (SIZE(512))
    MAX-ACCESS  read-only
    STATUS      current
    DESCRIPTION
            "This object allows the manager to retrieve the
              Issuer Name."
    ::= { McardcertificationEntry 4 }

VividlogicMcardSzManCertSubjectName OBJECT-TYPE
    SYNTAX      DisplayString (SIZE(512))
    MAX-ACCESS  read-only
    STATUS      current
    DESCRIPTION
            "This object allows the manager to retrieve the
            ManCertSubjectName info ."
    ::= { McardcertificationEntry 5 }

VividlogicMcardSzManCertIssuerName OBJECT-TYPE
    SYNTAX      DisplayString (SIZE(512))
    MAX-ACCESS  read-only
    STATUS      current
    DESCRIPTION
            "This object allows the manager to retrieve the
             ManCertIssuerName."
    ::= { McardcertificationEntry 6 }

VividlogicMcardAcHostId OBJECT-TYPE
    SYNTAX      DisplayString (SIZE(5))
    MAX-ACCESS  read-only
    STATUS      current
    DESCRIPTION
            "This object allows the manager to retrieve the
            Host ID Id."
    ::= { McardcertificationEntry 7 }

VividlogicMcardbCertAvailable OBJECT-TYPE
    SYNTAX      DisplayString (SIZE(4))                                                                                    
    MAX-ACCESS  read-only                                                                            
    STATUS      current                                                                                                               
    DESCRIPTION
            "The value 'Yes' indicates that the Certification Avilable
             . 'No' means the No Certification Not Avilable."
    ::= { McardcertificationEntry 8 }

VividlogicMcardbCertValid OBJECT-TYPE
    SYNTAX      DisplayString (SIZE(4))
    MAX-ACCESS  read-only
    STATUS      current
    DESCRIPTION
            "The value 'Yes' indicates that the Certification Valied
             . 'No' means the No Certification Not Valied."
    ::= { McardcertificationEntry 9 }

VividlogicMcardbVerifiedWithChain OBJECT-TYPE
    SYNTAX      DisplayString (SIZE(4))
    MAX-ACCESS  read-only
    STATUS      current
    DESCRIPTION
            "The value 'Yes' indicates that the verifedwith chain
             . 'No' means the No verifedwith chain."
    ::= { McardcertificationEntry 10 }
VividlogicMcardbIsProduction OBJECT-TYPE
    SYNTAX      DisplayString (SIZE(4))
    MAX-ACCESS  read-only
    STATUS      current
    DESCRIPTION
            "The value 'Yes' indicates that the production
             . 'No' means the No Production."
    ::= { McardcertificationEntry 11 }


END
