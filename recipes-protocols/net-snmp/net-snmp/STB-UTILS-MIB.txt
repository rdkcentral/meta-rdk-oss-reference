-- File Name : STB-UTILS-MIB
-- Date      : Fri Oct 25 16:11:11 IST 2013
-- Author    : SeaChange India
-- Directory : /mnt/nfs/bin/target-snmp/share/snmp/mibs


STB-UTILS-MIB	DEFINITIONS ::= BEGIN
	IMPORTS
		xcalibur
			FROM COMCAST-SMI
		RowStatus, DisplayString
			FROM SNMPv2-TC
		DisplayString
			FROM RFC1213-MIB
		MODULE-IDENTITY, OBJECT-IDENTITY, OBJECT-TYPE, Integer32,enterprises
			FROM SNMPv2-SMI;

	--  1.3.6.4.1.17270.9225.1
	stbHostUtils	MODULE-IDENTITY
		LAST-UPDATED	"201004131613Z"
		ORGANIZATION	"Organization"
		CONTACT-INFO	"Contact-info"
		DESCRIPTION	"Description"
		REVISION	"201004131613Z"
		DESCRIPTION	""
		::=  {  xcalibur  1  }

	--  1.3.6.4.1.17270.9225.1.4
	ocap	OBJECT IDENTIFIER
		::=  {  stbHostUtils  4  }

	--  1.3.6.4.1.17270.9225.1.4.2
	stbUtils	OBJECT IDENTIFIER
		::=  {  ocap  3  }

	currentChannelNumber  OBJECT-TYPE
		SYNTAX                  DisplayString
		MAX-ACCESS              read-only
		STATUS                  current
		DESCRIPTION             "Integer - Current Channel Number e.g. '2266'"
		::=  {  stbUtils  1  }

	currentServiceType  OBJECT-TYPE
		SYNTAX                  DisplayString
		MAX-ACCESS              read-only
		STATUS                  current
		DESCRIPTION             "String- Currently tuned service type e.g. ' Linear, DVR or VOD'"
		::=  {  stbUtils  2  }

	currentChEncryptionStatus  OBJECT-TYPE
		SYNTAX                  DisplayString
		MAX-ACCESS              read-only
		STATUS                  current
		DESCRIPTION             "String Encryption status of currently playing content(encrypted or unencrypted)"
		::=  {  stbUtils  3  }
	
	deviceFriendlyName  OBJECT-TYPE
		SYNTAX                  DisplayString
		MAX-ACCESS              read-only
		STATUS                  current
		DESCRIPTION             "String - Device Friendly name"
		::=  {  stbUtils  4  }

	currentZoomOption  OBJECT-TYPE
		SYNTAX                  DisplayString
		MAX-ACCESS              read-only
		STATUS                  current
		DESCRIPTION             "String - Current Zoom options(Full/ None)."
		::=  {  stbUtils  5  }

	channelLockStatus  OBJECT-TYPE
		SYNTAX                  DisplayString
		MAX-ACCESS              read-only
		STATUS                  current
		DESCRIPTION             "String - Channel locked status( Locked / Un-locked)."
		::=  {  stbUtils  6  }

	parentalControlStatus  OBJECT-TYPE
		SYNTAX                  DisplayString
		MAX-ACCESS              read-only
		STATUS                  current
		DESCRIPTION             "String - Parental control settings status(pin challenged or not)."
		::=  {  stbUtils  7  }

	closedCaptionState  OBJECT-TYPE
		SYNTAX                  DisplayString
		MAX-ACCESS              read-only
		STATUS                  current
		DESCRIPTION             "String:  Closed caption state(On/Off)"
		::=  {  stbUtils  8  }

	closedCaptionColor  OBJECT-TYPE
		SYNTAX                  DisplayString
		MAX-ACCESS              read-only
		STATUS                  current
		DESCRIPTION             "String: Closed caption attributes(Color)"
		::=  {  stbUtils  9  }

	closedCaptionFont  OBJECT-TYPE
		SYNTAX                  DisplayString
		MAX-ACCESS              read-only
		STATUS                  current
		DESCRIPTION             "String: Closed caption attributes(Font)"
		::=  {  stbUtils  10  }

	closedCaptionOpacity  OBJECT-TYPE
		SYNTAX                  DisplayString
		MAX-ACCESS              read-only
		STATUS                  current
		DESCRIPTION             "String - Closed caption attributes(Opacity)"
		::=  {  stbUtils  11  }

	easState  OBJECT-TYPE
		SYNTAX                  DisplayString
		MAX-ACCESS              read-only
		STATUS                  current
		DESCRIPTION             "String -  EAS state - (Message inprogress, received, not in-progress)"
		::=  {  stbUtils  12  }

	fpRecordLedStatus  OBJECT-TYPE
		SYNTAX                  DisplayString
		MAX-ACCESS              read-only
		STATUS                  current
		DESCRIPTION             "String - FP LED Status (ON or OFF -> Record)"
		::=  {  stbUtils  13  }


	fpPowerLedStatus  OBJECT-TYPE
		SYNTAX                  DisplayString
		MAX-ACCESS              read-only
		STATUS                  current
		DESCRIPTION             "String - FP LED Status (ON or OFF ->  Power)"
		::=  {  stbUtils  14  }

END
